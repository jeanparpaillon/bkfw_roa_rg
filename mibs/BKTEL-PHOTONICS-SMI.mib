BKTEL-PHOTONICS-SMI DEFINITIONS ::= BEGIN

IMPORTS
    MODULE-IDENTITY, OBJECT-IDENTITY, enterprises
	FROM SNMPv2-SMI;

bktelPhotonics MODULE-IDENTITY
    LAST-UPDATED "201412110000Z"
    ORGANIZATION "BKtel Photonics SAS"
    CONTACT-INFO
            "   BKtel Photonics SAS
	    	website: www.bktel-photonics.com
		email: legoas@bktel.com
		contact: Cyril Le Goas"
    DESCRIPTION
            "The MIB module as BKtel Photonics enterprise products."

    REVISION      "201412110000Z"
    DESCRIPTION
		"Initial revision."
    ::= { enterprises 44890 }

END

SMM-MIB DEFINITIONS ::= BEGIN

IMPORTS
    MODULE-IDENTITY, OBJECT-TYPE, Gauge32, Integer32, NOTIFICATION-TYPE
	FROM SNMPv2-SMI

    NOTIFICATION-GROUP
	FROM SNMPv2-CONF

    TEXTUAL-CONVENTION, DisplayString, DateAndTime, RowStatus
    	FROM SNMPv2-TC

    bktelPhotonics
	FROM BKTEL-PHOTONICS-SMI;

smmModule MODULE-IDENTITY
    LAST-UPDATED "201605240000Z"
    ORGANIZATION "BKtel Photonics"
    CONTACT-INFO
            "   BKtel Photonics
	    	website: www.bktel-photonics.com
		email: photonics@bktel.com"
    DESCRIPTION
            "The MIB module to describe commands for BKtel Photonics Supervision Management Module."

    REVISION      "201410170000Z"
    DESCRIPTION
	"Initial revision."
    REVISION	"201412140000Z"
    DESCRIPTION
	"Update traps definitions."
    REVISION	"201501120000Z"
    DESCRIPTION
	"Add 2 MCU traps."
    REVISION	"201501170000Z"
    DESCRIPTION
	"Fix trap names (regarding SMM and AMP)."
    REVISION	"201501300000Z"
    DESCRIPTION
	"Add traps: smmPsu1Trap and smmPsu2Trap."
    REVISION	"201502300000Z"
    DESCRIPTION
	"Fix typo in smmPsu2Trap description."
    REVISION	"201605240000Z"
    DESCRIPTION
	"Add PSU, FAN{1,2,3,4} traps."
    REVISION	"201605240000Z"
    DESCRIPTION
	"Add laser #2 current and current consigns.
	Remove amp identity."
    REVISION    "202205060000Z"
    DESCRIPTION
    "Change precision of following variables to 0.1:
    * smmPowerSupply
    * smmOutputPowerConsign
    * ampGainConsign
    * ampOutputPowerConsign
    * ampCurInternalTemp
    * ampPowerPd1
    * ampPowerPd2
    * ampPowerPd3
    * ampPowerSupply
    * ampInputLossTh
    * ampOutputLossTh
    * ampPCMin
    * ampPCMax
    * ampGCMin
    * ampGCMax

    Change following variables syntax:
    * ampPCMin: Integer32
    * ampPCMax: Integer32
    * ampOutputPowerConsign: Integer32
    "
    REVISION   "202212190000Z"
    DESCRIPTION
    "Add new fields fields to amp table:
    * overallGain
    * gainBeforeVoa
    * voaAttenuation
    "
    ::= { bktelPhotonics 1 }

smmMIB	OBJECT IDENTIFIER ::= { smmModule 1 }
smmMIBObjects OBJECT IDENTIFIER ::= { smmMIB 1 }
smmMIBTraps OBJECT IDENTIFIER ::= { smmMIB 2 }
smmMIBConformance OBJECT IDENTIFIER ::= { smmMIB 3 }

smm OBJECT IDENTIFIER ::= { smmMIBObjects 1 }

-- Datatypes

-- Managed Objects

smmVendor	OBJECT-TYPE
    SYNTAX	DisplayString
    MAX-ACCESS	read-only
    STATUS	current
    DESCRIPTION
	"SMM vendor."
    ::= { smm 1 }

smmModuleType	OBJECT-TYPE
    SYNTAX	DisplayString
    MAX-ACCESS	read-only
    STATUS	current
    DESCRIPTION
	"SMM type."
    ::= { smm 2 }

smmHWVer	OBJECT-TYPE
    SYNTAX	DisplayString
    MAX-ACCESS	read-only
    STATUS	current
    DESCRIPTION
	"SMM hardware version."
    ::= { smm 3 }

smmHWRev	OBJECT-TYPE
    SYNTAX	DisplayString
    MAX-ACCESS	read-only
    STATUS	current
    DESCRIPTION
	"SMM hardware revision."
    ::= { smm 4 }

smmSWVer	OBJECT-TYPE
    SYNTAX	DisplayString
    MAX-ACCESS	read-only
    STATUS	current
    DESCRIPTION
	"SMM software version."
    ::= { smm 5 }

smmFWVer	OBJECT-TYPE
    SYNTAX	DisplayString
    MAX-ACCESS	read-only
    STATUS	current
    DESCRIPTION
	"SMM firmware version."
    ::= { smm 6 }

smmPartNum	OBJECT-TYPE
    SYNTAX	DisplayString
    MAX-ACCESS	read-only
    STATUS	current
    DESCRIPTION
	"SMM part number."
    ::= { smm 7 }

smmSerialNum	OBJECT-TYPE
    SYNTAX	DisplayString
    MAX-ACCESS	read-only
    STATUS	current
    DESCRIPTION
	"SMM serial number."
    ::= { smm 8 }

smmProductDate	OBJECT-TYPE
    SYNTAX	DisplayString
    MAX-ACCESS	read-only
    STATUS	current
    DESCRIPTION
	"SMM production date."
    ::= { smm 9 }

smmPowerSupply	OBJECT-TYPE
    SYNTAX	Integer32
    MAX-ACCESS	read-only
    STATUS	current
    DESCRIPTION
	"The SMM power supply voltage, in tenth (0.1) of V."
    ::= { smm 10 }

smmCurInternalTemp	OBJECT-TYPE
    SYNTAX	Integer32
    MAX-ACCESS	read-only
    STATUS	current
    DESCRIPTION
	"The SMM internal temperature, in tenth (0.1) of °C."
    ::= { smm 11 }

smmNumber OBJECT-TYPE
    SYNTAX      Integer32
    MAX-ACCESS  read-only
    STATUS      current
    DESCRIPTION
	"The number of amplifiers present on the system."
    ::= { smm 12 }

-- the Amp table

ampTable OBJECT-TYPE
    SYNTAX	SEQUENCE OF AmpEntry
    MAX-ACCESS	not-accessible
    STATUS	current
    DESCRIPTION
	"A list of Amplifier entries. The number of entries is 
	given by the value of AmpNumber."
    ::= { smm 13 }

ampEntry OBJECT-TYPE
    SYNTAX	AmpEntry
    MAX-ACCESS	not-accessible
    STATUS	current
    DESCRIPTION
	"An entry containing management information applicable to a particular Amplifier."
    INDEX	{ ampIndex }
    ::= { ampTable 1 }

AmpEntry ::=
	SEQUENCE {
		ampIndex			INTEGER,
		ampAmpConsign	 	Gauge32,
		ampAmpConsign2	 	Gauge32,
		ampGainConsign		Integer32,
		ampOutputPowerConsign	Integer32,
		ampOperatingMode		INTEGER,
		ampCurLaserTemp		Integer32,
		ampCurAmp			Gauge32,
		ampCurAmp2			Gauge32,
		ampCurInternalTemp		Integer32,
		ampPowerPd1            	Integer32,
		ampPowerPd2            	Integer32,
		ampPowerPd3            	Integer32,
		ampPowerSupply         	Integer32,
		ampInputLossTh    		Integer32,
		ampOutputLossTh        	Integer32,
		ampCCMax1			Gauge32,
		ampCCMax2			Gauge32,
		ampPCMin            Integer32,
		ampPCMax			Integer32,
		ampGCMin			Gauge32,
		ampGCMax			Gauge32,
        ampOverallGain         Integer32,
        ampGainBeforeVoa       Integer32,
        ampVoaAttenuation      Integer32
	}

ampIndex OBJECT-TYPE
    SYNTAX    	INTEGER
    MAX-ACCESS	read-only
    STATUS	current
    DESCRIPTION
	"A unique value, greater than zero, for each amplifier."
    ::= { ampEntry 1 }

ampAmpConsign OBJECT-TYPE
    SYNTAX	Gauge32
    MAX-ACCESS	read-write
    STATUS	current
    DESCRIPTION
	"The value of the laser current consign used in current control mode, in mA."
    ::= { ampEntry 2 }

ampAmpConsign2 OBJECT-TYPE
    SYNTAX	Gauge32
    MAX-ACCESS	read-write
    STATUS	current
    DESCRIPTION
	"The value of the 2nd laser current consign used in current control mode, in mA."
    ::= { ampEntry 3 }

ampGainConsign OBJECT-TYPE
    SYNTAX	Integer32
    MAX-ACCESS	read-write
    STATUS	current
    DESCRIPTION
	"The value of the lasers gain consign used in gain control mode, in 0.1 dBm."
    ::= { ampEntry 4 }

ampOutputPowerConsign OBJECT-TYPE
    SYNTAX	Integer32
    MAX-ACCESS	read-write
    STATUS	current
    DESCRIPTION
	"The value of the lasers output power consign used in output power control mode, in 0.1 dBm."
    ::= { ampEntry 5 }

ampOperatingMode OBJECT-TYPE
    SYNTAX	INTEGER {
            pc(1),
		    gc(2),
		    cc(3),
		    off(4)
		    }
    MAX-ACCESS	read-write
    STATUS	current
    DESCRIPTION
	"The current operational mode of the laser."
    ::= { ampEntry 6 }

ampCurLaserTemp	OBJECT-TYPE
    SYNTAX	Integer32
    MAX-ACCESS	read-only
    STATUS	current
    DESCRIPTION
	"The current laser temperature."
    ::= { ampEntry 7 }

ampCurAmp	OBJECT-TYPE
    SYNTAX	Gauge32
    MAX-ACCESS	read-only
    STATUS	current
    DESCRIPTION
	"The current laser #1 electrical current."
    ::= { ampEntry 8 }

ampCurAmp2	OBJECT-TYPE
    SYNTAX	Gauge32
    MAX-ACCESS	read-only
    STATUS	current
    DESCRIPTION
	"The current laser #2 electrical current."
    ::= { ampEntry 9 }

ampCurInternalTemp	OBJECT-TYPE
    SYNTAX	Integer32
    MAX-ACCESS	read-only
    STATUS	current
    DESCRIPTION
	"The current internal temperature, in tenth (0.1) of °C."
    ::= { ampEntry 10 }

ampPowerPd1	OBJECT-TYPE
    SYNTAX	Integer32
    MAX-ACCESS	read-only
    STATUS	current
    DESCRIPTION
	"The power level on the monitoring photodiode(1)."
    ::= { ampEntry 11 }

ampPowerPd2	OBJECT-TYPE
    SYNTAX	Integer32
    MAX-ACCESS	read-only
    STATUS	current
    DESCRIPTION
	"The power level on the monitoring photodiode(2)."
    ::= { ampEntry 12 }

ampPowerPd3	OBJECT-TYPE
    SYNTAX	Integer32
    MAX-ACCESS	read-only
    STATUS	current
    DESCRIPTION
	"The power level on the monitoring photodiode(3)."
    ::= { ampEntry 13 }

ampPowerSupply	OBJECT-TYPE
    SYNTAX	Integer32
    MAX-ACCESS	read-only
    STATUS	current
    DESCRIPTION
	"The power supply voltage, in 0.1 V."
    ::= { ampEntry 14 }

ampInputLossTh	OBJECT-TYPE
    SYNTAX	Integer32
    MAX-ACCESS	read-write
    STATUS	current
    DESCRIPTION
	"The loss of input power threshold, in 0.1 dBm."
    ::= { ampEntry 15 }

ampOutputLossTh OBJECT-TYPE
    SYNTAX	Integer32
    MAX-ACCESS	read-write
    STATUS	current
    DESCRIPTION
	"The loss of output power threshold, in 0.1 dBm."
    ::= { ampEntry 16 }

ampCCMax1 OBJECT-TYPE
    SYNTAX	Gauge32
    MAX-ACCESS	read-only
    STATUS	current
    DESCRIPTION
	"Maximal consign for laser #1 in CC mode."
    ::= { ampEntry 17 }

ampCCMax2 OBJECT-TYPE
    SYNTAX	Gauge32
    MAX-ACCESS	read-only
    STATUS	current
    DESCRIPTION
	"Maximal consign for laser #2 in CC mode."
    ::= { ampEntry 18 }

ampPCMin OBJECT-TYPE
    SYNTAX	Integer32
    MAX-ACCESS	read-only
    STATUS	current
    DESCRIPTION
	"Minimal consign for laser #2 in PC mode."
    ::= { ampEntry 19 }

ampPCMax OBJECT-TYPE
    SYNTAX	Integer32
    MAX-ACCESS	read-only
    STATUS	current
    DESCRIPTION
	"Maximal consign for laser #2 in PC mode."
    ::= { ampEntry 20 }

ampGCMin OBJECT-TYPE
    SYNTAX	Gauge32
    MAX-ACCESS	read-only
    STATUS	current
    DESCRIPTION
	"Minimal consign for laser #2 in GC mode."
    ::= { ampEntry 21 }

ampGCMax OBJECT-TYPE
    SYNTAX	Gauge32
    MAX-ACCESS	read-only
    STATUS	current
    DESCRIPTION
	"Maximal consign for laser #2 in GC mode."
    ::= { ampEntry 22 }

ampOverallGain OBJECT-TYPE
    SYNTAX Integer32
    MAX-ACCESS read-only
    STATUS current
    DESCRIPTION
    "Overall Gain."
    ::= { ampEntry 23 }

ampGainBeforeVoa OBJECT-TYPE
    SYNTAX Integer32
    MAX-ACCESS read-only
    STATUS current
    DESCRIPTION
    "Gain Before VOA."
    ::= { ampEntry 24 }

ampVoaAttenuation OBJECT-TYPE
    SYNTAX Integer32
    MAX-ACCESS read-only
    STATUS current
    DESCRIPTION
    "VOA Attenuation."
    ::= { ampEntry 25 }

ampInputPowerTrap NOTIFICATION-TYPE
    OBJECTS {
    	ampIndex,
	ampPowerPd1
    }
    STATUS current
    DESCRIPTION
	"Loss of input power alarm"
    ::= { smmMIBTraps 1 }

ampOutputPowerTrap NOTIFICATION-TYPE
    OBJECTS {
        ampIndex,
	ampPowerPd2
    }
    STATUS current
    DESCRIPTION
	"Loss of output power alarm"
    ::= { smmMIBTraps 2 }

ampPumpTempTrap NOTIFICATION-TYPE
    OBJECTS {
        ampIndex,
	ampCurLaserTemp
    }
    STATUS current
    DESCRIPTION
	"Pump temperature alarm"
    ::= { smmMIBTraps 3 }

ampPumpBiasTrap NOTIFICATION-TYPE
    OBJECTS {
        ampIndex,
	ampCurAmp
    }
    STATUS current
    DESCRIPTION
	"Laser current is over 95% of EOL"
    ::= { smmMIBTraps 4 }

ampInternalTempTrap NOTIFICATION-TYPE
    OBJECTS {
        ampIndex,
	ampCurInternalTemp
    }
    STATUS current
    DESCRIPTION
	"Amp Internal temperature alarm"
    ::= { smmMIBTraps 5 }

ampPowerSupplyTrap NOTIFICATION-TYPE
    OBJECTS {
        ampIndex,
	ampPowerSupply
    }
    STATUS current
    DESCRIPTION
	"Amp Power supply alarm"
    ::= { smmMIBTraps 6 }

smmInternalTempTrap NOTIFICATION-TYPE
    OBJECTS {
	smmCurInternalTemp
    }
    STATUS current
    DESCRIPTION
	"smm Internal temperature alarm"
    ::= { smmMIBTraps 7 }

smmPowerSupplyTrap NOTIFICATION-TYPE
    OBJECTS {
	smmPowerSupply
    }
    STATUS current
    DESCRIPTION
	"SMM Power supply alarm"
    ::= { smmMIBTraps 8 }

ampBrefTrap NOTIFICATION-TYPE
    OBJECTS {
        ampIndex,
	ampPowerPd2,
	ampPowerPd3
    }
    STATUS current
    DESCRIPTION
	"Back reflection alarm"
    ::= { smmMIBTraps 9 }

ampAdiTrap NOTIFICATION-TYPE
    OBJECTS {
        ampIndex
    }
    STATUS current
    DESCRIPTION
	"Shutdown input active"
    ::= { smmMIBTraps 10 }

ampMuteTrap NOTIFICATION-TYPE
    OBJECTS {
        ampIndex
    }
    STATUS current
    DESCRIPTION
	"Mute input is active"
    ::= { smmMIBTraps 11 }

smmGenericTrap NOTIFICATION-TYPE
    STATUS current
    DESCRIPTION
	"Generic SMM trap (for testing purpose mainly)"
    ::= { smmMIBTraps 12 }

smmPsu1Trap NOTIFICATION-TYPE
    STATUS current
    DESCRIPTION
	"Default detected on PSU nr. 1"
    ::= { smmMIBTraps 13 }

smmPsu2Trap NOTIFICATION-TYPE
    STATUS current
    DESCRIPTION
	"Default detected on PSU nr. 2"
    ::= { smmMIBTraps 14 }

smmPsuTrap NOTIFICATION-TYPE
    STATUS current
    DESCRIPTION
	"Default detected on PSU"
    ::= { smmMIBTraps 15 }

smmFan1Trap NOTIFICATION-TYPE
    STATUS current
    DESCRIPTION
	"Default detected on FAN #1"
    ::= { smmMIBTraps 16 }

smmFan2Trap NOTIFICATION-TYPE
    STATUS current
    DESCRIPTION
	"Default detected on FAN #2"
    ::= { smmMIBTraps 17 }

smmFan3Trap NOTIFICATION-TYPE
    STATUS current
    DESCRIPTION
	"Default detected on FAN #3"
    ::= { smmMIBTraps 18 }

smmFan4Trap NOTIFICATION-TYPE
    STATUS current
    DESCRIPTION
	"Default detected on FAN #4"
    ::= { smmMIBTraps 19 }

smmMIBTrapGroups OBJECT IDENTIFIER ::= { smmMIBConformance 1 }

smmMIBTrapGroup NOTIFICATION-GROUP
    NOTIFICATIONS {
        ampInputPowerTrap,
		ampOutputPowerTrap,
		ampPumpTempTrap,
		ampPumpBiasTrap,
		ampInternalTempTrap,
		ampPowerSupplyTrap,
		smmInternalTempTrap,
		smmPowerSupplyTrap,
		ampBrefTrap,
		ampAdiTrap,
		ampMuteTrap,
		smmGenericTrap,
		smmPsu1Trap,
		smmPsu2Trap,
		smmPsuTrap,
		smmFan1Trap,
		smmFan2Trap,
		smmFan3Trap,
		smmFan4Trap
    }
    STATUS current
    DESCRIPTION
	"The notifications generated by SMM."
    ::= { smmMIBTrapGroups 1 }

END

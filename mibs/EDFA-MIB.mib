EDFA-MIB DEFINITIONS ::= BEGIN

IMPORTS
    MODULE-IDENTITY, OBJECT-TYPE, Gauge32, Integer32, NOTIFICATION-TYPE
	FROM SNMPv2-SMI

    NOTIFICATION-GROUP
	FROM SNMPv2-CONF

    TEXTUAL-CONVENTION, DisplayString, DateAndTime, RowStatus
    	FROM SNMPv2-TC

    bktelPhotonics
	FROM BKTEL-PHOTONICS-SMI;

edfaModule MODULE-IDENTITY
    LAST-UPDATED "201501120000Z"
    ORGANIZATION "BKtel Photonics"
    CONTACT-INFO
            "   BKtel Photonics
	    	website: www.bktel-photonics.com
		email: photonics@bktel.com"
    DESCRIPTION
            "The MIB module to describe commands for BKtel Photonics EDFA."

    REVISION      "201410170000Z"
    DESCRIPTION
	"Initial revision."
    REVISION	"201412140000Z"
    DESCRIPTION
	"Update traps definitions."
    REVISION	"201501120000Z"
    DESCRIPTION
	"Add 2 MCU traps."
    ::= { bktelPhotonics 1 }

edfaMIB	OBJECT IDENTIFIER ::= { edfaModule 1 }
edfaMIBObjects OBJECT IDENTIFIER ::= { edfaMIB 1 }
edfaMIBTraps OBJECT IDENTIFIER ::= { edfaMIB 2 }
edfaMIBConformance OBJECT IDENTIFIER ::= { edfaMIB 3 }

edfa OBJECT IDENTIFIER ::= { edfaMIBObjects 1 }

-- Datatypes

-- Managed Objects

edfaVendor	OBJECT-TYPE
    SYNTAX	DisplayString
    MAX-ACCESS	read-only
    STATUS	current
    DESCRIPTION
	"EDFA vendor."
    ::= { edfa 1 }

edfaModuleType	OBJECT-TYPE
    SYNTAX	DisplayString
    MAX-ACCESS	read-only
    STATUS	current
    DESCRIPTION
	"EDFA type."
    ::= { edfa 2 }

edfaHWVer	OBJECT-TYPE
    SYNTAX	DisplayString
    MAX-ACCESS	read-only
    STATUS	current
    DESCRIPTION
	"EDFA hardware version."
    ::= { edfa 3 }

edfaHWRev	OBJECT-TYPE
    SYNTAX	DisplayString
    MAX-ACCESS	read-only
    STATUS	current
    DESCRIPTION
	"EDFA hardware revision."
    ::= { edfa 4 }

edfaSWVer	OBJECT-TYPE
    SYNTAX	DisplayString
    MAX-ACCESS	read-only
    STATUS	current
    DESCRIPTION
	"EDFA software version."
    ::= { edfa 5 }

edfaFWVer	OBJECT-TYPE
    SYNTAX	DisplayString
    MAX-ACCESS	read-only
    STATUS	current
    DESCRIPTION
	"EDFA firmware version."
    ::= { edfa 6 }

edfaPartNum	OBJECT-TYPE
    SYNTAX	DisplayString
    MAX-ACCESS	read-only
    STATUS	current
    DESCRIPTION
	"EDFA part number."
    ::= { edfa 7 }

edfaSerialNum	OBJECT-TYPE
    SYNTAX	DisplayString
    MAX-ACCESS	read-only
    STATUS	current
    DESCRIPTION
	"EDFA serial number."
    ::= { edfa 8 }

edfaProductDate	OBJECT-TYPE
    SYNTAX	DisplayString
    MAX-ACCESS	read-only
    STATUS	current
    DESCRIPTION
	"EDFA production date."
    ::= { edfa 9 }

edfaPowerSupply	OBJECT-TYPE
    SYNTAX	Integer32
    MAX-ACCESS	read-only
    STATUS	current
    DESCRIPTION
	"The EDFA power supply voltage."
    ::= { edfa 10 }

edfaCurInternalTemp	OBJECT-TYPE
    SYNTAX	Integer32
    MAX-ACCESS	read-only
    STATUS	current
    DESCRIPTION
	"The EDFA internal temperature."
    ::= { edfa 11 }

edfaNumber OBJECT-TYPE
    SYNTAX      Integer32
    MAX-ACCESS  read-only
    STATUS      current
    DESCRIPTION
	"The number of EDFA present on the system."
    ::= { edfa 12 }

-- the EDFA table

edfaMcuTable OBJECT-TYPE
    SYNTAX	SEQUENCE OF EdfaMcuEntry
    MAX-ACCESS	not-accessible
    STATUS	current
    DESCRIPTION
	"A list of MCU entries. The number of entries is 
	given by the value of mcuNumber."
    ::= { edfa 13 }

edfaMcuEntry OBJECT-TYPE
    SYNTAX	EdfaMcuEntry
    MAX-ACCESS	not-accessible
    STATUS	current
    DESCRIPTION
	"An entry containing management information applicable to a 
	particular MCU."
    INDEX	{ edfaMcuIndex }
    ::= { edfaMcuTable 1 }

EdfaMcuEntry ::=
	SEQUENCE {
		edfaMcuIndex			INTEGER,
		edfaMcuAmpConsign	 	Gauge32,
		edfaMcuGainConsign		Integer32,
		edfaMcuOutputPowerConsign	Gauge32,
		edfaMcuOperatingMode		INTEGER,
		edfaMcuCurLaserTemp		Integer32,
		edfaMcuCurAmp			Gauge32,
		edfaMcuCurInternalTemp		Integer32,
		edfaMcuPowerPd1            	Integer32,
		edfaMcuPowerPd2            	Integer32,
		edfaMcuPowerPd3            	Integer32,
		edfaMcuPowerSupply         	Integer32,
		edfaMcuInputLossTh    		Integer32,
		edfaMcuOutputLossTh        	Integer32,
		edfaMcuVendor			DisplayString,
		edfaMcuModuleType		DisplayString,
		edfaMcuHWVer			DisplayString,
		edfaMcuHWRev			DisplayString,
		edfaMcuSWVer			DisplayString,
		edfaMcuFWVer			DisplayString,
		edfaMcuPartNum			DisplayString,
		edfaMcuSerialNum		DisplayString,
		edfaMcuProductDate		DateAndTime
	}

edfaMcuIndex OBJECT-TYPE
    SYNTAX    	INTEGER
    MAX-ACCESS	read-only
    STATUS	current
    DESCRIPTION
	"A unique value, greater than zero, for each MCU."
    ::= { edfaMcuEntry 1 }

edfaMcuAmpConsign OBJECT-TYPE
    SYNTAX	Gauge32
    MAX-ACCESS	read-write
    STATUS	current
    DESCRIPTION
	"The value of the lasers current consign used in current control mode, in mA."
    ::= { edfaMcuEntry 2 }

edfaMcuGainConsign OBJECT-TYPE
    SYNTAX	Integer32
    MAX-ACCESS	read-write
    STATUS	current
    DESCRIPTION
	"The value of the lasers gain consign used in gain control mode, in dBm."
    ::= { edfaMcuEntry 3 }

edfaMcuOutputPowerConsign OBJECT-TYPE
    SYNTAX	Gauge32
    MAX-ACCESS	read-write
    STATUS	current
    DESCRIPTION
	"The value of the lasers output power consign used in output power control mode, in dBm."
    ::= { edfaMcuEntry 4 }

edfaMcuOperatingMode OBJECT-TYPE
    SYNTAX	INTEGER {
                    pc(1),
		    gc(2),
		    cc(3),
		    off(4)
		    }
    MAX-ACCESS	read-write
    STATUS	current
    DESCRIPTION
	"The current operational mode of the laser."
    ::= { edfaMcuEntry 5 }

edfaMcuCurLaserTemp	OBJECT-TYPE
    SYNTAX	Integer32
    MAX-ACCESS	read-only
    STATUS	current
    DESCRIPTION
	"The current laser temperature."
    ::= { edfaMcuEntry 6 }

edfaMcuCurAmp	OBJECT-TYPE
    SYNTAX	Gauge32
    MAX-ACCESS	read-only
    STATUS	current
    DESCRIPTION
	"The current laser electrical current."
    ::= { edfaMcuEntry 7 }

edfaMcuCurInternalTemp	OBJECT-TYPE
    SYNTAX	Integer32
    MAX-ACCESS	read-only
    STATUS	current
    DESCRIPTION
	"The current internal temperature."
    ::= { edfaMcuEntry 8 }

edfaMcuPowerPd1	OBJECT-TYPE
    SYNTAX	Integer32
    MAX-ACCESS	read-only
    STATUS	current
    DESCRIPTION
	"The power level on the monitoring photodiode(1)."
    ::= { edfaMcuEntry 9 }

edfaMcuPowerPd2	OBJECT-TYPE
    SYNTAX	Integer32
    MAX-ACCESS	read-only
    STATUS	current
    DESCRIPTION
	"The power level on the monitoring photodiode(2)."
    ::= { edfaMcuEntry 10 }

edfaMcuPowerPd3	OBJECT-TYPE
    SYNTAX	Integer32
    MAX-ACCESS	read-only
    STATUS	current
    DESCRIPTION
	"The power level on the monitoring photodiode(3)."
    ::= { edfaMcuEntry 11 }

edfaMcuPowerSupply	OBJECT-TYPE
    SYNTAX	Integer32
    MAX-ACCESS	read-only
    STATUS	current
    DESCRIPTION
	"The power supply voltage."
    ::= { edfaMcuEntry 12 }

edfaMcuInputLossTh	OBJECT-TYPE
    SYNTAX	Integer32
    MAX-ACCESS	read-only
    STATUS	current
    DESCRIPTION
	"The loss of input power threshold."
    ::= { edfaMcuEntry 13 }

edfaMcuOutputLossTh OBJECT-TYPE
    SYNTAX	Integer32
    MAX-ACCESS	read-only
    STATUS	current
    DESCRIPTION
	"The loss of output power threshold."
    ::= { edfaMcuEntry 14 }

edfaMcuVendor	OBJECT-TYPE
    SYNTAX	DisplayString
    MAX-ACCESS	read-only
    STATUS	current
    DESCRIPTION
	"Module vendor."
    ::= { edfaMcuEntry 15 }

edfaMcuModuleType	OBJECT-TYPE
    SYNTAX	DisplayString
    MAX-ACCESS	read-only
    STATUS	current
    DESCRIPTION
	"Module type."
    ::= { edfaMcuEntry 16 }

edfaMcuHWVer	OBJECT-TYPE
    SYNTAX	DisplayString
    MAX-ACCESS	read-only
    STATUS	current
    DESCRIPTION
	"Module hardware version."
    ::= { edfaMcuEntry 17 }

edfaMcuHWRev	OBJECT-TYPE
    SYNTAX	DisplayString
    MAX-ACCESS	read-only
    STATUS	current
    DESCRIPTION
	"Module hardware revision."
    ::= { edfaMcuEntry 18 }

edfaMcuSWVer	OBJECT-TYPE
    SYNTAX	DisplayString
    MAX-ACCESS	read-only
    STATUS	current
    DESCRIPTION
	"Module software version."
    ::= { edfaMcuEntry 19 }

edfaMcuFWVer	OBJECT-TYPE
    SYNTAX	DisplayString
    MAX-ACCESS	read-only
    STATUS	current
    DESCRIPTION
	"Module firmware version."
    ::= { edfaMcuEntry 20 }

edfaMcuPartNum	OBJECT-TYPE
    SYNTAX	DisplayString
    MAX-ACCESS	read-only
    STATUS	current
    DESCRIPTION
	"Module part number."
    ::= { edfaMcuEntry 21 }

edfaMcuSerialNum	OBJECT-TYPE
    SYNTAX	DisplayString
    MAX-ACCESS	read-only
    STATUS	current
    DESCRIPTION
	"Module serial number."
    ::= { edfaMcuEntry 22 }

edfaMcuProductDate	OBJECT-TYPE
    SYNTAX	DisplayString
    MAX-ACCESS	read-only
    STATUS	current
    DESCRIPTION
	"Module production date."
    ::= { edfaMcuEntry 23 }

edfaInputPowerTrap NOTIFICATION-TYPE
    OBJECTS {
    	edfaMcuIndex,
	edfaMcuPowerPd1
    }
    STATUS current
    DESCRIPTION
	"Loss of input power alarm"
    ::= { edfaMIBTraps 1 }

edfaOutputPowerTrap NOTIFICATION-TYPE
    OBJECTS {
        edfaMcuIndex,
	edfaMcuPowerPd2
    }
    STATUS current
    DESCRIPTION
	"Loss of output power alarm"
    ::= { edfaMIBTraps 2 }

edfaPumpTempTrap NOTIFICATION-TYPE
    OBJECTS {
        edfaMcuIndex,
	edfaMcuCurLaserTemp
    }
    STATUS current
    DESCRIPTION
	"Pump temperature alarm"
    ::= { edfaMIBTraps 3 }

edfaPumpBiasTrap NOTIFICATION-TYPE
    OBJECTS {
        edfaMcuIndex,
	edfaMcuCurAmp
    }
    STATUS current
    DESCRIPTION
	"Laser current is over 95% of EOL"
    ::= { edfaMIBTraps 4 }

edfaMcuInternalTempTrap NOTIFICATION-TYPE
    OBJECTS {
        edfaMcuIndex,
	edfaCurInternalTemp
    }
    STATUS current
    DESCRIPTION
	"MCU Internal temperature alarm"
    ::= { edfaMIBTraps 5 }

edfaMcuPowerSupplyTrap NOTIFICATION-TYPE
    OBJECTS {
        edfaMcuIndex,
	edfaPowerSupply
    }
    STATUS current
    DESCRIPTION
	"MCU Power supply alarm"
    ::= { edfaMIBTraps 6 }

edfaInternalTempTrap NOTIFICATION-TYPE
    OBJECTS {
	edfaCurInternalTemp
    }
    STATUS current
    DESCRIPTION
	"EDFA Internal temperature alarm"
    ::= { edfaMIBTraps 7 }

edfaPowerSupplyTrap NOTIFICATION-TYPE
    OBJECTS {
	edfaPowerSupply
    }
    STATUS current
    DESCRIPTION
	"EDFA Power supply alarm"
    ::= { edfaMIBTraps 8 }

edfaBrefTrap NOTIFICATION-TYPE
    OBJECTS {
        edfaMcuIndex,
	edfaMcuPowerPd2,
	edfaMcuPowerPd3
    }
    STATUS current
    DESCRIPTION
	"Back reflection alarm"
    ::= { edfaMIBTraps 9 }

edfaAdiTrap NOTIFICATION-TYPE
    OBJECTS {
        edfaMcuIndex
    }
    STATUS current
    DESCRIPTION
	"Shutdown input active"
    ::= { edfaMIBTraps 10 }

edfaMuteTrap NOTIFICATION-TYPE
    OBJECTS {
        edfaMcuIndex
    }
    STATUS current
    DESCRIPTION
	"Mute input is active"
    ::= { edfaMIBTraps 11 }

edfaGenericTrap NOTIFICATION-TYPE
    STATUS current
    DESCRIPTION
	"Generic EDFA trap (for testing purpose mainly)"
    ::= { edfaMIBTraps 12 }

edfaMIBTrapGroups OBJECT IDENTIFIER ::= { edfaMIBConformance 1 }

edfaMIBTrapGroup NOTIFICATION-GROUP
    NOTIFICATIONS {
        edfaInputPowerTrap,
	edfaOutputPowerTrap,
	edfaPumpTempTrap,
	edfaPumpBiasTrap,
	edfaMcuInternalTempTrap,
	edfaMcuPowerSupplyTrap,
	edfaInternalTempTrap,
	edfaPowerSupplyTrap,
	edfaBrefTrap,
	edfaAdiTrap,
	edfaMuteTrap,
	edfaGenericTrap
    }
    STATUS current
    DESCRIPTION
	"The notifications generated by EDFA."
    ::= { edfaMIBTrapGroups 1 }

END
